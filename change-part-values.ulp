#usage "<b>Global Search/Replace Part Values</b> - v1.00 (02/28/2010)<p>"
       "This ULP generates a script to replaces all part values that match "
       "a given search value with a new user specified part value."
       "<p>"
       "<author>http://www.bobstarr.net</author>";

//////////////////////////////////////////////////////////////////////////////
//
// GLOBAL SEARCH/REPLACE PART VALUE(S)
//
// Copyright (C) 2009-2010, Robert E. Starr (http://www.bobstarr.net)
// 
// REVISION HISTORY:
//
// v1.00 - 05/14/2009 (RES) - Initial Release
//
//////////////////////////////////////////////////////////////////////////////
//
// THIS PROGRAM IS PROVIDED AS IS AND WITHOUT WARRANTY OF ANY KIND,
// EXPRESSED OR IMPLIED.
//
//////////////////////////////////////////////////////////////////////////////

string Version = "1.00";

string fileName;

int fScriptExec = 0;    // execute script automatically after generating

string strOldValue = "(TBD)";
string strNewValue = "(TBD)";

//////////////////////////////////////////////////////////////////////////////
// trim all spaces from a string

string trimSpaces(string source)
{
    if (!source)
        return source;
    string result;
    int i;
    int cnt=0;
    for (i=0; source[i]; i++) {
      if (isspace(source[i]))
          continue;
      result[cnt] = source[i];
      cnt++;
    }
    return result;
}

// trim spaces on left and on right of string

string trimString(string source) {
  if(!source) return source;
  string result;
  int i, head = 0;
  for (i = 0; source[i]; i++) {
    if (!isspace(source[i])) {
      head = i;
      break;
    }
  }
  int send = strlen(source);
  int len = send;
  if (len) {
    for (i = len-1; i >= 0; i--) {
      if (!isspace(source[i])) {
        send = i+1;
        break;
      }
    }
  }
  return strsub(source, head, send-head);
}


//////////////////////////////////////////////////////////////////////////////
// Normalize Upper Case - force all other VALUE fields to upper case

int doReplaceValue(UL_PART part)
{
    string strValue  = trimString(part.value);
    string strNewVal = trimString(strNewValue);

    if (strValue == strOldValue)
    {
        printf("# replace '%s' from '%s' to '%s'\n", part.name, strValue, strNewVal);
        printf("VALUE %s '%s';\n\n", part.name, strNewVal);
        return 1;
    }

    return 0;
}

//////////////////////////////////////////////////////////////////////////////
// Script Entry Point

if (schematic)
{

    schematic(SCH)
    {
        fileName = filesetext(SCH.name, "_ChangePartValue~~~.scr");

        string title = "Search/Replace Part Values v" + Version;

        int Result = dlgDialog(title)
        {
            dlgHBoxLayout
            {
                dlgGroup("Global Search/Replace Value")
                {
                    dlgGridLayout
                    {
                        dlgCell(1,0) dlgLabel("Find all part(s) with value:");
                        dlgCell(1,1) dlgStringEdit(strOldValue);

                        dlgCell(2,0) dlgLabel("Repace with new value:");
                        dlgCell(2,1) dlgStringEdit(strNewValue);
                    }
                }
            }

            dlgHBoxLayout
            {
                dlgPushButton("OK") dlgAccept();
                dlgPushButton("-Cancel") dlgReject();
                dlgCheckBox("&Execute Script", fScriptExec);
            }
        };

        if (!Result)
            exit(0);

        output(fileName, "wtD")
        {
            printf("# 'generated by change-part-values.ulp v%s, exported from;\n", Version);
            printf("# '%s at %s;\n", SCH.name, t2string(time()));
            printf("# '%s;\n\n", EAGLE_SIGNATURE);

            SCH.sheets(S)
            {
                printf("#\n# SHEET %d - NORMALIZE PART VALUES\n#\n", S.number);
                printf("EDIT .s%d\n", S.number);

                S.parts(P)
                {
                    if (P.device.package && P.name)
                    {
                        // Otherwise force all value text to upper case
                        doReplaceValue(P);
                    }
                }
            }

            printf("EDIT .s1\n");
        }

        if (fScriptExec)
            exit ("SCRIPT '" + fileName + "';");
        else
            exit(0);
    }
}
else
{
    dlgMessageBox("Start this ULP in Schematic!", "OK");
}

// End-Of-File
