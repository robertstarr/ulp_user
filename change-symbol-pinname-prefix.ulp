#usage "<b>Change char in symbol pin names</b>\n"
       "<p>This script loops through all symbols in a library and changes any character in the PIN name to a new character.<p>"
       "<author>Author: http://www.bobstarr.net</author>"

string ulp_path = "";
string script_change = "";
string strPrefixRemove = "P$";
string strPrefixAdd = "";
int Result = 0;

// Trim leading and trailing white space characters
string TrimWhiteSpace(string s)
{
    while (s && isspace(s[0]))
        s = strsub(s, 1);
    while (s && isspace(s[strlen(s) - 1]))
        s = strsub(s, 0, strlen(s) - 1);
    return s;
}

// Trim prefix from the pad name
string TrimPrefix(string s)
{
    string remove = TrimWhiteSpace(strPrefixRemove);
    int lenremove = strlen(remove);
    int pos = strstr(s, remove);
    if (pos >= 0)
        s = strsub(s, lenremove);

    // add new prefix if needed
    string add = TrimWhiteSpace(strPrefixAdd);
    string temp = s;
    if (strlen(add))
        temp = add+s;
       
    return temp;
}

// new text sizes/ratios in mils

void DoSymbol(UL_SYMBOL S) {
    string name;
    S.pins(P) {
        printf("NAME '%s' '%s'\n", P.name, TrimPrefix(P.name));        
    } 
}

void menue()
{
   dlgDialog("Change Symbol Pin Prefix") {
         dlgGroup("Replace Pinname Char") {
            dlgHBoxLayout { dlgLabel("Remove Prefix :\t"); dlgStringEdit(strPrefixRemove); }
            dlgHBoxLayout { dlgLabel("Replace with  :\t"); dlgStringEdit(strPrefixAdd); }
         }
      dlgPushButton("+&OK")     { dlgAccept(); return; }
      dlgPushButton("-&Cancel") { dlgReject(); exit (0);}
   };
}

if (library) {
   char bkslash = '/';
   int pos = strrchr(argv[0], bkslash);
   if (pos >= 0) {
      ulp_path = strsub(argv[0], 0, pos + 1);
   }
   int n = 0;
   library(L) {
   int posb = strrchr(argv[0], bkslash);
   if (posb >= 0) {
      ulp_path = strsub(argv[0], 0, posb + 1);
   }

   menue();

   script_change = filesetext(L.name, "~~~.scr");

   output(script_change, "wtD") {
      printf("DISPLAY 95 96;\n");

      int firstf = 1;

      if (symbol) symbol(S) {
         DoSymbol(S);
      }
      else
      {	
        L.symbols(S) {
           printf("EDIT %s.SYM;\n", S.name);
           DoSymbol(S);
        }
      }

   }
   }
  exit ("SCRIPT '" + script_change + "';\n");
} else {
   dlgMessageBox("\n*** Start this ULP in a Library ***\n");
   exit (0);
}
